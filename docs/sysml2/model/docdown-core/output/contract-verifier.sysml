package DocDownCore {
    part def ContractVerifier {
        doc /* Reconciles a finished scratch folder against its own manifest and reports any divergence. */

        comment sourceRef /* Source: src/DemaConsulting.DocDown.Core/Output/ContractVerifier.cs */
        comment testRef /* Test: test/DemaConsulting.DocDown.Core.Tests/Output/ContractVerifierTests.cs */
        comment designRef /* Design: docs/design/docdown-core/output/contract-verifier.md */
        comment verificationRef /* Verification: docs/verification/docdown-core/output/contract-verifier.md */
        comment reqRef /* Requirements: docs/reqstream/docdown-core/output/contract-verifier.yaml */
    }
}
