package DocDownExcel {
    part def ExcelDocDownBuilderExtensions {
        doc /* The registration seam: the one explicit, reflection-free call that adds the managed Open XML Excel backend to a DocDown builder. Free of any Open XML SDK type on its public surface. */

        comment sourceRef /* Source: src/DemaConsulting.DocDown.Excel/ExcelDocDownBuilderExtensions.cs */
        comment testRef /* Test: test/DemaConsulting.DocDown.Excel.Tests/ExcelDocDownBuilderExtensionsTests.cs */
        comment designRef /* Design: docs/design/docdown-excel/excel-doc-down-builder-extensions.md */
        comment verificationRef /* Verification: docs/verification/docdown-excel/excel-doc-down-builder-extensions.md */
        comment reqRef /* Requirements: docs/reqstream/docdown-excel/excel-doc-down-builder-extensions.yaml */
    }
}
