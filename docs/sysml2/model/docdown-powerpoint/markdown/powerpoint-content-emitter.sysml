package DocDownPowerPoint {
    part def PowerPointContentEmitter {
        doc /* The single emission path: turns a read deck model into the output contract, writing each slide's title, body text, and speaker notes in presentation order, plus the inline images, the content inventory, and the notes the model and options imply. */

        comment sourceRef /* Source: src/DemaConsulting.DocDown.PowerPoint/Markdown/PowerPointContentEmitter.cs */
        comment testRef /* Test: test/DemaConsulting.DocDown.PowerPoint.Tests/Markdown/PowerPointContentEmitterTests.cs */
        comment designRef /* Design: docs/design/docdown-powerpoint/markdown/powerpoint-content-emitter.md */
        comment verificationRef /* Verification: docs/verification/docdown-powerpoint/markdown/powerpoint-content-emitter.md */
        comment reqRef /* Requirements: docs/reqstream/docdown-powerpoint/markdown/powerpoint-content-emitter.yaml */
    }
}
