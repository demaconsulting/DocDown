package DocDownPowerPoint {
    part def PowerPointOpenXmlExtractor {
        doc /* The managed backend the engine selects and invokes for a .pptx content extraction: declares its priority, declares that this extractor does not provide rendering, probes unconditionally, buffers and opens the deck, reads it into the model, delegates emission to the shared emitter, and contributes the self-tests. */

        comment sourceRef /* Source: src/DemaConsulting.DocDown.PowerPoint/OpenXml/PowerPointOpenXmlExtractor.cs */
        comment testRef /* Test: test/DemaConsulting.DocDown.PowerPoint.Tests/OpenXml/PowerPointOpenXmlExtractorTests.cs */
        comment designRef /* Design: docs/design/docdown-powerpoint/open-xml/powerpoint-open-xml-extractor.md */
        comment verificationRef /* Verification: docs/verification/docdown-powerpoint/open-xml/powerpoint-open-xml-extractor.md */
        comment reqRef /* Requirements: docs/reqstream/docdown-powerpoint/open-xml/powerpoint-open-xml-extractor.yaml */
    }
}
