package DocDownPowerPoint {
    part def PowerPointDocDownBuilderExtensions {
        doc /* The reflection-free registration seam: AddPowerPoint registers both the managed Open XML backend and the COM automation backend on a DocDownBuilder. */

        comment sourceRef /* Source: src/DemaConsulting.DocDown.PowerPoint/PowerPointDocDownBuilderExtensions.cs */
        comment testRef /* Test: test/DemaConsulting.DocDown.PowerPoint.Tests/PowerPointDocDownBuilderExtensionsTests.cs */
        comment designRef /* Design: docs/design/docdown-powerpoint/powerpoint-doc-down-builder-extensions.md */
        comment verificationRef /* Verification: docs/verification/docdown-powerpoint/powerpoint-doc-down-builder-extensions.md */
        comment reqRef /* Requirements: docs/reqstream/docdown-powerpoint/powerpoint-doc-down-builder-extensions.yaml */
    }
}
