package DocDownOffice {
    private import SoftwareItemMetadata::*;

    doc
    /*
     * DemaConsulting.DocDown.PowerPoint is the PowerPoint extraction subsystem of DemaConsulting.DocDown.Office: a backend that
     * reads a deck's slide text, titles, speaker notes, slide order, and embedded images and metadata
     * into the DocDown output contract. The text, titles, speaker notes, and slide order are always
     * extracted from the file itself; rendered slide images are a separate, opt-in concern provided by
     * the DemaConsulting.DocDown.PowerPoint.Rendering package. It has two child subsystems (Markdown, OpenXml) and one direct
     * unit (PowerPointDocDownBuilderExtensions).
     */

    part def PowerPoint {
        doc /* The DemaConsulting.DocDown.PowerPoint subsystem as a whole. */

        metadata info : SoftwareInfo {
            testFiles = ("test/DemaConsulting.DocDown.Office.Tests/PowerPoint/DocDownPowerPointTests.cs");
            designFiles = ("docs/design/docdown-office/powerpoint.md");
            verificationFiles = ("docs/verification/docdown-office/powerpoint.md");
            requirementFiles = ("docs/reqstream/docdown-office/powerpoint.yaml");
        }

        part powerPointDocDownBuilderExtensions : PowerPointDocDownBuilderExtensions;
        part markdown : PowerPointMarkdown;
        part openXml : PowerPointOpenXml;
    }
}
