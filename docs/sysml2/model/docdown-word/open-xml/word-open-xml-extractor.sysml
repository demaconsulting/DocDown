package DocDownWord {
    part def WordOpenXmlExtractor {
        doc /* The managed backend the engine selects and invokes: reads the document, emits content through the shared emitter as one continuous flow, and records the content inventory and the notes only it can explain. */

        comment sourceRef /* Source: src/DemaConsulting.DocDown.Word/OpenXml/WordOpenXmlExtractor.cs */
        comment testRef /* Test: test/DemaConsulting.DocDown.Word.Tests/OpenXml/WordOpenXmlExtractorTests.cs */
        comment designRef /* Design: docs/design/docdown-word/open-xml/word-open-xml-extractor.md */
        comment verificationRef /* Verification: docs/verification/docdown-word/open-xml/word-open-xml-extractor.md */
        comment reqRef /* Requirements: docs/reqstream/docdown-word/open-xml/word-open-xml-extractor.yaml */
    }
}
