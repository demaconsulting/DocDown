package DocDownWord {
    part def WordMarkdownWriter {
        doc /* Renders the backend-neutral document model to one markdown flow: headings, lists, inline formatting, image links, comments, footnotes, and the Document Control section, escaping markdown metacharacters. */

        comment sourceRef /* Source: src/DemaConsulting.DocDown.Word/Markdown/WordMarkdownWriter.cs */
        comment testRef /* Test: test/DemaConsulting.DocDown.Word.Tests/Markdown/WordMarkdownWriterTests.cs */
        comment designRef /* Design: docs/design/docdown-word/markdown/word-markdown-writer.md */
        comment verificationRef /* Verification: docs/verification/docdown-word/markdown/word-markdown-writer.md */
        comment reqRef /* Requirements: docs/reqstream/docdown-word/markdown/word-markdown-writer.yaml */
    }
}
