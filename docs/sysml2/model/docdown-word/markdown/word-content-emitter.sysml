package DocDownWord {
    part def WordContentEmitter {
        doc /* The model-to-sink emission path: writes the model's content (single-flow or per-part), images, the content inventory, and notes through the sink. */

        comment sourceRef /* Source: src/DemaConsulting.DocDown.Word/Markdown/WordContentEmitter.cs */
        comment testRef /* Test: test/DemaConsulting.DocDown.Word.Tests/Markdown/WordContentEmitterTests.cs */
        comment designRef /* Design: docs/design/docdown-word/markdown/word-content-emitter.md */
        comment verificationRef /* Verification: docs/verification/docdown-word/markdown/word-content-emitter.md */
        comment reqRef /* Requirements: docs/reqstream/docdown-word/markdown/word-content-emitter.yaml */
    }
}
