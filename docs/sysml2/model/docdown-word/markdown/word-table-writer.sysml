package DocDownWord {
    part def WordTableWriter {
        doc /* Renders a table model as a GitHub-Flavored-Markdown table: header and delimiter rows, padded short rows, escaped cell content, skipped empty tables, and flattened merged and nested cells with a flatten count. */

        comment sourceRef /* Source: src/DemaConsulting.DocDown.Word/Markdown/WordTableWriter.cs */
        comment testRef /* Test: test/DemaConsulting.DocDown.Word.Tests/Markdown/WordTableWriterTests.cs */
        comment designRef /* Design: docs/design/docdown-word/markdown/word-table-writer.md */
        comment verificationRef /* Verification: docs/verification/docdown-word/markdown/word-table-writer.md */
        comment reqRef /* Requirements: docs/reqstream/docdown-word/markdown/word-table-writer.yaml */
    }
}
