package DocDownWord {
    part def WordDocDownBuilderExtensions {
        doc /* The registration seam: explicit, reflection-free calls that add the Word backends to a DocDown builder. A direct unit of the DocDown.Word system. */

        comment sourceRef /* Source: src/DemaConsulting.DocDown.Word/WordDocDownBuilderExtensions.cs */
        comment testRef /* Test: test/DemaConsulting.DocDown.Word.Tests/WordDocDownBuilderExtensionsTests.cs */
        comment designRef /* Design: docs/design/docdown-word/word-doc-down-builder-extensions.md */
        comment verificationRef /* Verification: docs/verification/docdown-word/word-doc-down-builder-extensions.md */
        comment reqRef /* Requirements: docs/reqstream/docdown-word/word-doc-down-builder-extensions.yaml */
    }
}
