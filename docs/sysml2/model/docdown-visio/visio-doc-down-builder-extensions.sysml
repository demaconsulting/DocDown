package DocDownVisio {
    part def VisioDocDownBuilderExtensions {
        doc /* The one visible edge from a host to this package: the explicit, reflection-free AddVisio call that adds both the managed Open Packaging backend and the COM automation backend to a DocDownBuilder, registering factories so nothing is constructed and no environment is probed at registration. */

        comment sourceRef /* Source: src/DemaConsulting.DocDown.Visio/VisioDocDownBuilderExtensions.cs */
        comment testRef /* Test: test/DemaConsulting.DocDown.Visio.Tests/VisioDocDownBuilderExtensionsTests.cs */
        comment designRef /* Design: docs/design/docdown-visio/visio-doc-down-builder-extensions.md */
        comment verificationRef /* Verification: docs/verification/docdown-visio/visio-doc-down-builder-extensions.md */
        comment reqRef /* Requirements: docs/reqstream/docdown-visio/visio-doc-down-builder-extensions.yaml */
    }
}
